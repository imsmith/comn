module comn-secret {
  yang-version 1.1;
  namespace "urn:comn:secrets";
  prefix sec;

  import comn-types {
    prefix comn;
  }

  organization
    "COMN Project";

  contact
    "COMN Development Team
     Project repository: https://github.com/comn";

  description
    "This module defines cryptographic structures for the COMN system,
     including encrypted data blobs, key management, and secure containers.

     The module supports multiple encryption algorithms (AES-GCM, ChaCha20-Poly1305)
     and key types (Ed25519, RSA-4096, ECDSA-P256) with AEAD authentication
     for data integrity and authenticity.

     Security considerations:
     - All encryption uses AEAD ciphers for authenticated encryption
     - Nonces MUST be unique per encryption operation
     - Private key material should be handled with extreme care
     - Key hints use BLAKE2b to avoid leaking key metadata";

  revision 2025-12-27 {
    description
      "Initial revision of secret management data model.
       - AEAD encryption support
       - Multiple cipher algorithms
       - Key management structures
       - Strong typing for UUIDs and timestamps
       - Binary length constraints for cryptographic data";
    reference
      "RFC 5116: An Interface and Algorithms for Authenticated Encryption
       RFC 8439: ChaCha20 and Poly1305 for IETF Protocols";
  }

  typedef cipher-algorithm {
    type enumeration {
      enum aes-gcm {
        description
          "AES-256 in Galois/Counter Mode (GCM).
           Provides authenticated encryption with associated data (AEAD).
           Uses 256-bit keys, 96-bit nonces, and 128-bit authentication tags.";
        reference
          "NIST SP 800-38D: Recommendation for Block Cipher Modes of Operation";
      }
      enum chacha20-poly1305 {
        description
          "ChaCha20-Poly1305 AEAD cipher.
           Provides authenticated encryption with associated data (AEAD).
           Uses 256-bit keys, 96-bit nonces, and 128-bit authentication tags.
           Often preferred for software-only implementations due to better
           performance without hardware AES acceleration.";
        reference
          "RFC 8439: ChaCha20 and Poly1305 for IETF Protocols";
      }
    }
    description
      "Supported symmetric encryption algorithms.
       All algorithms provide AEAD (Authenticated Encryption with Associated Data).";
  }

  typedef key-algorithm {
    type enumeration {
      enum ed25519 {
        description
          "Ed25519 signature algorithm (recommended).
           Uses Curve25519 for fast, secure digital signatures.
           Public key: 32 bytes, Private key: 32 bytes, Signature: 64 bytes.
           Preferred for new implementations due to simplicity and security.";
        reference
          "RFC 8032: Edwards-Curve Digital Signature Algorithm (EdDSA)";
      }
      enum rsa-4096 {
        description
          "RSA with 4096-bit modulus.
           Traditional public-key algorithm with larger key sizes.
           Slower than Ed25519 but widely supported in legacy systems.";
        reference
          "RFC 8017: PKCS #1: RSA Cryptography Specifications Version 2.2";
      }
      enum ecdsa-p256 {
        description
          "ECDSA using NIST P-256 curve (secp256r1).
           Elliptic curve signature algorithm.
           Widely supported but Ed25519 is generally preferred for new work.";
        reference
          "FIPS 186-4: Digital Signature Standard (DSS)";
      }
    }
    description
      "Supported asymmetric key algorithms for signing and verification.

       Implementation requirements:
       - Ed25519: 32-byte private key, 32-byte public key
       - RSA-4096: 4096-bit modulus
       - ECDSA-P256: Valid P-256 curve points";
  }

  grouping locked-blob {
    description
      "Encrypted data blob with AEAD authentication.
       Represents encrypted data with all necessary cryptographic parameters
       for decryption and verification.";

    leaf cipher {
      type cipher-algorithm;
      mandatory true;
      description "Encryption algorithm used";
    }

    leaf encrypted {
      type binary;
      mandatory true;
      description
        "Encrypted data (variable length depending on plaintext size).
         Ciphertext output from AEAD encryption operation.";
    }

    leaf tag {
      type binary {
        length "16";
      }
      mandatory true;
      description
        "AEAD authentication tag (128-bit/16-byte).
         Verifies ciphertext + metadata integrity and authenticity.
         Required for all AEAD ciphers.";
    }

    leaf key-hint {
      type binary {
        length "17";
      }
      description
        "Self-describing key fingerprint (17 bytes total):
         - Byte 0: Algorithm (0x01=Ed25519, 0x02=RSA-4096, 0x03=ECDSA-P256)
         - Bytes 1-16: BLAKE2b hash of public key (128 bits)
         Provides fast key lookup without leaking key metadata.";
    }

    leaf nonce {
      type binary {
        length "12";
      }
      mandatory true;
      description
        "Nonce/IV used for encryption (96-bit/12-byte).
         Used by both AES-GCM and ChaCha20-Poly1305.
         Must be unique per encryption operation with the same key.
         SHOULD use a counter or random generation with collision detection.";
    }

    container metadata {
      description
        "Metadata about the locked blob.
         SHOULD be included as AEAD associated data for authentication.";

      leaf created-at {
        type comn:iso8601-timestamp;
        description "Timestamp when blob was encrypted";
      }

      leaf description {
        type string {
          length "0..1024";
        }
        description "Human-readable description of the encrypted content";
      }
    }
  }

  grouping container {
    description
      "Collection of locked blobs with metadata.
       Organizes related encrypted data into a single logical unit.";

    leaf id {
      type comn:uuid;
      mandatory true;
      description "Container identifier";
    }

    leaf-list blob-ids {
      type comn:uuid;
      description
        "References to LockedBlob instances by ID.
         Each ID corresponds to a locked blob managed by this container.";
    }

    container metadata {
      description "Container metadata";

      leaf name {
        type comn:non-empty-string;
        description "Container name for identification";
      }

      leaf created-at {
        type comn:iso8601-timestamp;
        description "Timestamp when container was created";
      }

      leaf description {
        type string {
          length "0..1024";
        }
        description "Human-readable description of the container's purpose";
      }
    }
  }

  grouping key {
    description
      "Cryptographic key pair for signing and verification.
       Supports multiple key algorithms with appropriate size constraints.";

    leaf id {
      type binary;
      mandatory true;
      description
        "Key identifier/fingerprint.
         Used for key lookup and management.";
    }

    leaf algorithm {
      type key-algorithm;
      mandatory true;
      description "Key algorithm";
    }

    leaf public {
      type binary;
      mandatory true;
      description
        "Public key material.
         Size depends on algorithm:
         - Ed25519: 32 bytes
         - RSA-4096: ~512 bytes (DER format)
         - ECDSA-P256: 33 bytes (compressed) or 65 bytes (uncompressed)";
    }

    must "(algorithm = 'ed25519' and string-length(public) = 32) or " +
         "algorithm != 'ed25519'" {
      error-message "Ed25519 public keys must be exactly 32 bytes";
      error-app-tag "invalid-key-size";
      description
        "Business rule: Ed25519 public key size validation.
         Ensures cryptographic parameters match algorithm requirements.";
    }

    leaf private {
      type binary;
      description
        "Private key material (HIGHLY SENSITIVE).
         May be absent for public-only keys.

         Size depends on algorithm:
         - Ed25519: 32 bytes
         - RSA-4096: ~512 bytes (DER format)
         - ECDSA-P256: 32 bytes

         Security requirements:
         - MUST be encrypted at rest
         - MUST be encrypted in transit
         - MUST NOT appear in logs, error messages, or debug output
         - Access MUST be restricted to authorized processes only
         - SHOULD use secure memory (mlock) when loaded
         - SHOULD be cleared from memory immediately after use";
    }

    must "not(private) or " +
         "(algorithm = 'ed25519' and string-length(private) = 32) or " +
         "algorithm != 'ed25519'" {
      error-message "Ed25519 private keys must be exactly 32 bytes when present";
      error-app-tag "invalid-key-size";
      description
        "Business rule: Ed25519 private key size validation.
         Ensures cryptographic parameters match algorithm requirements.";
    }

    container metadata {
      description "Key metadata";

      leaf created-at {
        type comn:iso8601-timestamp;
        description "Timestamp when key was created or imported";
      }

      leaf description {
        type string {
          length "0..1024";
        }
        description "Human-readable description of the key's purpose";
      }

      leaf source {
        type enumeration {
          enum file {
            description "Key loaded from file system";
          }
          enum environment {
            description "Key loaded from environment variable";
          }
          enum context {
            description "Key loaded from execution context";
          }
          enum generated {
            description "Key generated by the system";
          }
          enum imported {
            description "Key imported from external source";
          }
        }
        description
          "Key source/origin.
           Tracks where the key material came from.";
      }
    }
  }
}
