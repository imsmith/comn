module comn-infra-health {
  yang-version 1.1;
  namespace "urn:comn:infra:health";
  prefix health;

  import comn-types {
    prefix comn;
  }

  organization
    "COMN Project";

  contact
    "COMN Development Team
     Project repository: https://github.com/comn";

  description
    "This module defines the data model for infrastructure health checks
     in the COMN system. Health checks monitor component availability,
     performance, and operational status.";

  revision 2025-12-27 {
    description
      "Initial revision.
       - Define health statuses: healthy, degraded, unhealthy
       - Support for latency tracking
       - Extensible details for component-specific health information
       - Strong typing for timestamps";
    reference
      "COMN Health Monitoring Specification";
  }

  typedef health-status {
    type enumeration {
      enum healthy {
        description
          "Component is fully operational and performing within
           expected parameters";
      }
      enum degraded {
        description
          "Component is operational but experiencing issues or
           performing below expected parameters. May require attention.";
      }
      enum unhealthy {
        description
          "Component is not operational or has failed critical checks.
           Immediate intervention required.";
      }
    }
    description
      "Health status classification for infrastructure components.
       Represents the operational state based on health check results.";
  }

  grouping health-check {
    description
      "Health check result structure for infrastructure components.
       Captures the status, timing, and details of health assessments.";

    leaf component {
      type comn:non-empty-string;
      mandatory true;
      description
        "Component being checked.
         Examples: 'database', 'cache', 'api', 'queue', 'storage'";
    }

    leaf status {
      type health-status;
      mandatory true;
      description "Health status determined by the check";
    }

    leaf message {
      type string {
        length "0..1024";
      }
      description
        "Status message or error information.
         Provides human-readable context about the health status.";
    }

    leaf latency-ms {
      type uint32;
      units "milliseconds";
      description
        "Health check execution time in milliseconds.
         Useful for detecting performance degradation.";
    }

    leaf timestamp {
      type comn:iso8601-timestamp;
      mandatory true;
      description
        "Timestamp when the health check was performed.
         Used for tracking check frequency and staleness.";
    }

    container details {
      description
        "Additional health details specific to the component type.
         May include metrics, connection counts, error rates, etc.";
      // Backend-specific health information
    }
  }
}
